VARIOUS_TESTS DEFINITIONS::=
BEGIN


SequenceNameClashTest ::= [43] SEQUENCE {
	myseqof [1] SEQUENCE OF UntaggedInteger,
	untaggedInteger CHOICE {
		myInteger [2] UntaggedInteger,
		myBoolean [3] BOOLEAN
	} OPTIONAL,
	myChoice CHOICE {
		myInteger [4] UntaggedInteger,
		myChoice2 [5] CHOICE {
			myInteger [6] UntaggedInteger,
			myBoolean [7] BOOLEAN
		},
		mySequence [8] SEQUENCE {
			myInteger [9] UntaggedInteger,
			myBoolean [10] BOOLEAN
		},
		myseqof [1] SEQUENCE OF UntaggedInteger
    },
	sequenceNameClashTest [8] SEQUENCE {
   	myInteger [9] UntaggedInteger,
   	myBoolean [10] BOOLEAN
  }
}

UntaggedInteger ::= INTEGER

IntegerListAndConstraint ::= INTEGER { oneMilliSec(1) } (0..65535)

IntegerList ::= INTEGER { oneMilliSec(1) }

IntegerConstraint ::= INTEGER (0..65535)

EnumerationWithoutValue ::= ENUMERATED {
	value1,
	value2
}

IntTest ::= INTEGER

InTestCst ::= INTEGER (1..10)

IntTestNegCst ::= INTEGER (-1..10)

IntTestSingleValue ::= INTEGER (1 | 5)

RealTest ::= REAL 

RealTestRange1 ::= REAL (-1.0 .. 2.0)

RealTestRange2 ::= REAL (-9E-10..1E6)

RealTestRange3 ::=	 REAL (0.0 .. 7.0E-2)

OctetStringConstraint1 ::=  OCTET STRING (SIZE( 1))  ('55'H)

OctetStringConstraint2 ::=  OCTET STRING (SIZE( 1))  ('10'B)

END
